CS2-classes {itu-t(0) identified-organization(4) etsi(0) inDomain(1) in-network(1) cs2(20) modules(0) in-cs2-classes (4) version1(0)}

DEFINITIONS ::= BEGIN

	IMPORTS
		ROS-OBJECT-CLASS,
		CONTRACT,
		OPERATION-PACKAGE,
		Code,
		OPERATION,
		CONNECTION-PACKAGE
	FROM Remote-Operations-Information-Objects  ros-InformationObjects
		emptyBind,
		emptyUnbind
	FROM Remote-Operations-Useful-Definitions  ros-UsefulDefinitions
		id-package-emptyConnection,
		id-rosObject-scf,
		id-rosObject-cusf,
		id-rosObject-dssp,
		id-rosObject-srf,
		id-rosObject-ssf,
		ros-InformationObjects,
		ros-UsefulDefinitions,
		ssf-scf-Protocol,
		-- scf-cusf-Protocol,
		-- scf-scf-Protocol,
		scf-srf-Protocol,
		-- scf-sdf-Protocol,
		datatypes
	FROM CS2-object-identifiers
			{itu-t(0) identified-organization(4) etsi(0) inDomain(1) in-network(1) cs2(20) modules(0) in-cs2-object-identifiers (17) version1(0)}
		inCs2AssistHandoffssfToScf,
		inCs2ScfToSsfGeneric,
		inCs2ScfToSsfTrafficManagement,
		inCs2SsfToScfGeneric,
		inCs2SsfToScfServiceManagement
	FROM CS2-SSF-SCF-pkgs-contracts-acs ssf-scf-Protocol
	--	cusf-scf-contract,
	--	scf-cusf-contract
	-- FROM CS2-SCF-CUSF-pkgs-contracts-acs scf-cusf-Protocol
	--	dsspContract,
	--	scf-scfContract
	-- FROM CS2-SCF-SCF-pkgs-contracts-acs srf-scf-contract
		srf-scf-contract
	FROM CS2-SCF-SRF-pkgs-contracts-acs scf-srf-Protocol
	--	dapContract
	-- FROM CS2-SCF-SDF-Protocol scf-sdf-Protocol
		CriticalityType
	FROM CS2-datatypes datatypes;

	ssf ROS-OBJECT-CLASS ::= {
		INITIATES {
			inCs2SsfToScfGeneric
			| inCs2AssistHandoffssfToScf
			| inCs2SsfToScfServiceManagement
		}
		RESPONDS {
			inCs2ScfToSsfGeneric
			| inCs2ScfToSsfTrafficManagement
			| inCs2SsfToScfServiceManagement
		}
		ID			id-rosObject-ssf
	}

	srf ROS-OBJECT-CLASS ::= {
		INITIATES {
			srf-scf-contract
		}
		ID			id-rosObject-srf
	}
	--cusf ROS-OBJECT-CLASS ::= {
	--	INITIATES	{cusf-scf-contract}
	--	RESPONDS	{scf-cusf-contract}
	--	ID			id-rosObject-cusf}
	--dssp ROS-OBJECT-CLASS ::= {
	--	BOTH		{dsspContract}
	--	ID			id-rosObject-dssp
	--	}

	scf ROS-OBJECT-CLASS ::= {
		INITIATES {
			inCs2ScfToSsfGeneric
			| inCs2ScfToSsfTrafficManagement
			| inCs2ScfToSsfServiceManagement
			| inCs2ScfToSsfTriggerManagement
	-- scf to cusf contracts
	--		| scf-cusf-contract
	-- scf to scf contracts
	--		| scf-scfContract
	--		| dsspContract
	-- sdf to scf contracts
	--		dapContract
		}
		RESPONDS	{
			inCs2SsfToScfGeneric
			| inCs2AssistHandoffssfToScf
			| inCs2SsfToScfServiceManagement
	-- cusf to scf contracts
	--		| cusf-scf-contract
	-- srf to scf contracts
			| srf-scf-contract
	-- scf to scf contracts
	-- 	| scf-scfContract
	--		| dsspContract
		}
		ID			id-rosObject-scf
	}

	EXTENSION ::= CLASS {
		&ExtensionType,
		&criticality	CriticalityType DEFAULT ignore,
		&id	Code
		}
	WITH SYNTAX {
		EXTENSION-SYNTAX	&ExtensionType
		CRITICALITY			&criticality
		IDENTIFIED BY		&id
		}
	--
	-- Example of addition of an extension named 'Some Network Specific Indicator' of type
	-- BOOLEAN, with criticality 'abort' and to be identified as extension number 1
	-- Example of definition using the above information object class:
	--
	-- SomeNetworkSpecificIndicator EXTENSION ::= {
	-- 	EXTENSION-SYNTAX	BOOLEAN
	--	CRITICALITY			abort
	--	IDENTIFIED BY		local: 1
	--	}
	--
	-- Example of transfer syntax, using the ExtensionField datatype as specified in subclause 4.1.
	-- Assuming the value of the extension is set to TRUE, the extensions parameter
	-- becomes a Sequence of type INTEGER ::= 1, criticality ENUMERATED ::= 1 and value [1]
	-- EXPLICIT BOOLEAN ::= TRUE.
	--
	-- Use of Q.1400 defined Extension is for further study.
	-- In addition the extension mechanism marker is used to identify the future minor additions
	-- to INAP.
	--
	-- firstExtension EXTENSION ::= {
	-- 	EXTENSION-SYNTAX	NULL
	-- 	CRITICALITY			ignore
	-- 	IDENTIFIED BY		local: 1
	-- }
	-- firstExtension is just an example.
	SupportedExtensions EXTENSION ::= {
	--	firstExtension,
		...
		-- full set of network operator extensions
	}
	-- SupportedExtension is the full set of the network operator extensions.

	UISCRIPT ::= CLASS {
		&SpecificInfo  OPTIONAL,
		&Result        OPTIONAL,
		&id            Code
	}
	WITH SYNTAX {
		[WITH-SPECIFICINFO  &SpecificInfo]
		[WITH-RESULT        &Result]
		IDENTIFIED BY       &id
	}

	firstScript UISCRIPT ::= {
		IDENTIFIED BY local: 1
	}
	-- firstScript is just an example.
	SupportedUIScripts UISCRIPT ::= {
		firstScript,
		...
		-- full set of User Interaction script
	}
	-- SupportedUIScripts is the full set of User Interaction scripts.

	inEmptyUnbind OPERATION ::= {
		RETURN RESULT	FALSE
		ALWAYS RESPONDS	FALSE}
	emptyConnectionPackage CONNECTION-PACKAGE ::= {
		BIND	emptyBind
		UNBIND	inEmptyUnbind
		RESPONDER UNBIND 	TRUE
		ID		id-package-emptyConnection
		}
	PARAMETERS-BOUND ::= CLASS
	{
		&minAChBillingChargingLength				INTEGER,
		&maxAChBillingChargingLength				INTEGER,
		&minAssReleaseInfoLength					INTEGER,
		&maxAssReleaseInfoLength					INTEGER,
		&minAttributesLength						INTEGER,
		&maxAttributesLength						INTEGER,
		&minBackwardGVNSLength						INTEGER,
		&maxBackwardGVNSLength						INTEGER,
		&maxBearerCapabilityLength					INTEGER,
		&minCalledPartyBCDNumberLength				INTEGER,
		&maxCalledPartyBCDNumberLength				INTEGER,
		&minCalledPartyNumberLength					INTEGER,
		&maxCalledPartyNumberLength					INTEGER,
		&minCallingPartyBusinessGroupIDLength		INTEGER,
		&maxCallingPartyBusinessGroupIDLength		INTEGER,
		&minCallingPartyNumberLength				INTEGER,
		&maxCallingPartyNumberLength				INTEGER,
		&minCallingPartySubAddressLength			INTEGER,
		&maxCallingPartySubAddressLength			INTEGER,
		&minCallResultLength						INTEGER,
		&maxCallResultLength						INTEGER,
		&minCarrierLength							INTEGER,
		&maxCarrierLength							INTEGER,
		&maxCauseLength								INTEGER,
		&minCompReceivedInfoLength					INTEGER,
		&maxCompReceivedInfoLength					INTEGER,
		&minDigitsLength							INTEGER,
		&maxDigitsLength							INTEGER,
		&minDisplayInformationLength				INTEGER,
		&maxDisplayInformationLength				INTEGER,
		&minEventSpecificInformationChargingLength	INTEGER,
		&maxEventSpecificInformationChargingLength	INTEGER,
		&minEventTypeChargingLength					INTEGER,
		&maxEventTypeChargingLength					INTEGER,
		&minFCIbccCS1Length							INTEGER,
		&maxFCIbccCS1Length							INTEGER,
		&minFCIbccCS2Length							INTEGER,
		&maxFCIbccCS2Length							INTEGER,
		&minForwardGVNSLength						INTEGER,
		&maxForwardGVNSLength						INTEGER,
		&minGenericNameLength						INTEGER,
		&maxGenericNameLength						INTEGER,
		&minGenericNumberLength						INTEGER,
		&maxGenericNumberLength						INTEGER,
		&maxInitialTimeInterval						INTEGER,
		&maxINServiceCompatibilityIndLength			INTEGER,
		&minIPAvailableLength						INTEGER,
		&maxIPAvailableLength						INTEGER,
		&minIPSSPCapabilitiesLength					INTEGER,
		&maxIPSSPCapabilitiesLength					INTEGER,
		&minISDNAccessRelatedInformationLength		INTEGER,
		&maxISDNAccessRelatedInformationLength		INTEGER,
		&minLocationNumberLength					INTEGER,
		&maxLocationNumberLength					INTEGER,
		&minMailBoxIDLength							INTEGER,
		&maxMailBoxIDLength							INTEGER,
		&minMessageContentLength					INTEGER,
		&maxMessageContentLength					INTEGER,
		&minMidCallControlInfoNum					INTEGER,
		&maxMidCallControlInfoNum					INTEGER,
		&minOriginalCalledPartyIDLength				INTEGER,
		&maxOriginalCalledPartyIDLength				INTEGER,
		&minReasonLength							INTEGER,
		&maxReasonLength							INTEGER,
		&minReceivedInformationLength				INTEGER,
		&maxReceivedInformationLength 				INTEGER,
		&maxRecordedMessageUnits					INTEGER,
		&maxRecordingTime							INTEGER,
		&minRedirectingPartyIDLength				INTEGER,
		&maxRedirectingPartyIDLength				INTEGER,
		&minRegistratorIdentifierLength				INTEGER,
		&maxRegistratorIdentifierLength				INTEGER,
		&minRequestedUTSINum 						INTEGER,
		&maxRequestedUTSINum 						INTEGER,
		&minRouteListLength							INTEGER,
		&maxRouteListLength							INTEGER,
		&minScfIDLength								INTEGER,
		&maxScfIDLength								INTEGER,
		&minScfAddressLength						INTEGER,
		&maxScfAddressLength						INTEGER,
		&minSCIBillingChargingLength				INTEGER,
		&maxSCIBillingChargingLength				INTEGER,
		&minServiceInteractionIndicatorsLength		INTEGER,
		&maxServiceInteractionIndicatorsLength		INTEGER,
		&minSFBillingChargingLength					INTEGER,
		&maxSFBillingChargingLength					INTEGER,
		&minUSIInformationLength					INTEGER,
		&maxUSIInformationLength					INTEGER,
		&minUSIServiceIndicatorLength				INTEGER,
		&maxUSIServiceIndicatorLength				INTEGER,
		&numOfBCSMEvents							INTEGER,
		&numOfBCUSMEvents							INTEGER,
		&numOfChargingEvents						INTEGER,
		&numOfCSAs									INTEGER,
		&numOfCSs									INTEGER,
		&numOfExtensions							INTEGER,
		&numOfGenericNumbers						INTEGER,
		&numOfInServiceCompatibilityIndLength		INTEGER,
		&numOfLegs									INTEGER,
		&numOfMessageIDs							INTEGER,
		&maxAmount									INTEGER,
		&maxInitialUnitIncrement					INTEGER,
		&maxScalingFactor							INTEGER,
		&maxSegmentsPerDataInterval					INTEGER,
		&maxTimePerInterval							INTEGER,
		&maxUnitsPerDataInterval 					INTEGER,
		&maxUnitsPerInterval						INTEGER,
		&ub-maxUserCredit							INTEGER,
		&ub-nbCall									INTEGER
	}
	WITH SYNTAX
	{
		MINIMUM-FOR-ACH-BILLING-CHARGING			&minAChBillingChargingLength
		MAXIMUM-FOR-ACH-BILLING-CHARGING			&maxAChBillingChargingLength
		MINIMUM-FOR-ASSOCIATION-RELEASE-INFO		&minAssReleaseInfoLength
		MAXIMUM-FOR-ASSOCIATION-RELEASE-INFO		&maxAssReleaseInfoLength
		MINIMUM-FOR-ATTRIBUTES						&minAttributesLength
		MAXIMUM-FOR-ATTRIBUTES						&maxAttributesLength
		MAXIMUM-FOR-BACKWARD-GVNS					&minBackwardGVNSLength
		MAXIMUM-FOR-BACKWARD-GVNS					&maxBackwardGVNSLength
		MAXIMUM-FOR-BEARER-CAPABILITY				&maxBearerCapabilityLength
		MINIMUM-FOR-CALLED-PARTY-BCD-NUMBER			&minCalledPartyBCDNumberLength
		MAXIMUM-FOR-CALLED-PARTY-BCD-NUMBER			&maxCalledPartyBCDNumberLength
		MINIMUM-FOR-CALLED-PARTY-NUMBER				&minCalledPartyNumberLength
		MAXIMUM-FOR-CALLED-PARTY-NUMBER				&maxCalledPartyNumberLength
		MINIMUM-FOR-CALLING-PARTY-BUSINESS-GROUP-ID	&minCallingPartyBusinessGroupIDLength
		MAXIMUM-FOR-CALLING-PARTY-BUSINESS-GROUP-ID	&maxCallingPartyBusinessGroupIDLength
		MINIMUM-FOR-CALLING-PARTY-NUMBER			&minCallingPartyNumberLength
		MAXIMUM-FOR-CALLING-PARTY-NUMBER			&maxCallingPartyNumberLength
		MINIMUM-FOR-CALLING-PARTY-SUBADDRESS		&minCallingPartySubAddressLength
		MAXIMUM-FOR-CALLING-PARTY-SUBADDRESS		&maxCallingPartySubAddressLength
		MINIMUM-FOR-CALL-RESULT						&minCallResultLength
		MAXIMUM-FOR-CALL-RESULT						&maxCallResultLength
		MINIMUM-FOR-CARRIER							&minCarrierLength
		MAXIMUM-FOR-CARRIER							&maxCarrierLength
		MAXIMUM-FOR-CAUSE							&maxCauseLength
		MINIMUM-FOR-COMPONENT-RECEIVED-INFO			&minCompReceivedInfoLength
		MAXIMUM-FOR-COMPONENT-RECEIVED-INFO			&maxCompReceivedInfoLength
		MINIMUM-FOR-DIGITS							&minDigitsLength
		MAXIMUM-FOR-DIGITS							&maxDigitsLength
		MINIMUM-FOR-DISPLAY							&minDisplayInformationLength
		MAXIMUM-FOR-DISPLAY							&maxDisplayInformationLength
		MINIMUM-FOR-EVENT-SPECIFIC-CHARGING			&minEventSpecificInformationChargingLength
		MAXIMUM-FOR-EVENT-SPECIFIC-CHARGING			&maxEventSpecificInformationChargingLength
		MINIMUM-FOR-EVENT-TYPE-CHARGING				&minEventTypeChargingLength
		MAXIMUM-FOR-EVENT-TYPE-CHARGING				&maxEventTypeChargingLength
		MINIMUM-FOR-FCI-BILLING-CHARGING-CS-ONE		&minFCIbccCS1Length
		MAXIMUM-FOR-FCI-BILLING-CHARGING-CS-ONE		&maxFCIbccCS1Length
		MINIMUM-FOR-FCI-BILLING-CHARGING-CS-TWO		&minFCIbccCS2Length
		MAXIMUM-FOR-FCI-BILLING-CHARGING-CS-TWO		&maxFCIbccCS2Length
		MINIMUM-FOR-FORWARD-GVNS					&minForwardGVNSLength
		MAXIMUM-FOR-FORWARD-GVNS					&maxForwardGVNSLength
		MINIMUM-FOR-GENERIC-NAME					&minGenericNameLength
		MAXIMUM-FOR-GENERIC-NAME					&maxGenericNameLength
		MINIMUM-FOR-GENERIC-NUMBER					&minGenericNumberLength
		MAXIMUM-FOR-GENERIC-NUMBER					&maxGenericNumberLength
		MAXIMUM-FOR-INITIAL-TIME-INTERVAL			&maxInitialTimeInterval
		MAXIMUM-FOR-IN-SERVICE-COMPATIBILITY		&maxINServiceCompatibilityIndLength
		MINIMUM-FOR-IP-AVAILABLE					&minIPAvailableLength
		MAXIMUM-FOR-IP-AVAILABLE					&maxIPAvailableLength
		MINIMUM-FOR-IP-SSP-CAPABILITIES				&minIPSSPCapabilitiesLength
		MAXIMUM-FOR-IP-SSP-CAPABILITIES				&maxIPSSPCapabilitiesLength
		MINIMUM-FOR-ISDN-ACCESS-RELATED-INFO		&minISDNAccessRelatedInformationLength
		MAXIMUM-FOR-ISDN-ACCESS-RELATED-INFO		&maxISDNAccessRelatedInformationLength
		MINIMUM-FOR-LOCATION-NUMBER					&minLocationNumberLength
		MAXIMUM-FOR-LOCATION-NUMBER					&maxLocationNumberLength
		MINIMUM-FOR-MAIL-BOX-ID						&minMailBoxIDLength
		MAXIMUM-FOR-MAIL-BOX-ID						&maxMailBoxIDLength
		MINIMUM-FOR-MESSAGE-CONTENT					&minMessageContentLength
		MAXIMUM-FOR-MESSAGE-CONTENT					&maxMessageContentLength
		MINIMUM-FOR-MID-CALL-CONTROL-INFO			&minMidCallControlInfoNum
		MAXIMUM-FOR-MID-CALL-CONTROL-INFO			&maxMidCallControlInfoNum
		MINIMUM-FOR-ORIGINAL-CALLED-PARTY-ID		&minOriginalCalledPartyIDLength
		MAXIMUM-FOR-ORIGINAL-CALLED-PARTY-ID		&maxOriginalCalledPartyIDLength
		MINIMUM-FOR-REASON							&minReasonLength
		MAXIMUM-FOR-REASON							&maxReasonLength
		MINIMUM-FOR-RECEIVED-INFORMATION			&minReceivedInformationLength
		MAXIMUM-FOR-RECEIVED-INFORMATION			&maxReceivedInformationLength
		MAXIMUM-FOR-RECORDED-MESSAGE-UNITS			&maxRecordedMessageUnits
		MAXIMUM-FOR-RECORDING-TIME					&maxRecordingTime
		MINIMUM-FOR-REDIRECTING-ID					&minRedirectingPartyIDLength
		MAXIMUM-FOR-REDIRECTING-ID					&maxRedirectingPartyIDLength
		MINIMUM-FOR-REGISTRATOR-IDENTIFIER			&minRegistratorIdentifierLength
		MAXIMUM-FOR-REGISTRATOR-IDENTIFIER			&maxRegistratorIdentifierLength
		MINIMUM-FOR-REQUESTED-UTSI-NUM				&minRequestedUTSINum
		MAXIMUM-FOR-REQUESTED-UTSI-NUM				&maxRequestedUTSINum
		MINIMUM-FOR-ROUTE-LIST						&minRouteListLength
		MAXIMUM-FOR-ROUTE-LIST						&maxRouteListLength
		MINIMUM-FOR-SCF-ID							&minScfIDLength
		MAXIMUM-FOR-SCF-ID							&maxScfIDLength
		MINIMUM-FOR-SCF-ADDRESS						&minScfAddressLength
		MAXIMUM-FOR-SCF-ADDRESS						&maxScfAddressLength
		MINIMUM-FOR-SCI-BILLING-CHARGING			&minSCIBillingChargingLength
		MAXIMUM-FOR-SCI-BILLING-CHARGING			&maxSCIBillingChargingLength
		MINIMUM-FOR-SII								&minServiceInteractionIndicatorsLength
		MAXIMUM-FOR-SII								&maxServiceInteractionIndicatorsLength
		MINIMUM-FOR-SF-BILLING-CHARGING				&minSFBillingChargingLength
		MAXIMUM-FOR-SF-BILLING-CHARGING				&maxSFBillingChargingLength
		MINIMUM-FOR-USI-INFORMATION					&minUSIInformationLength
		MAXIMUM-FOR-USI-INFORMATION					&maxUSIInformationLength
		MINIMUM-FOR-USI-SERVICE-INDICATOR			&minUSIServiceIndicatorLength
		MAXIMUM-FOR-USI-SERVICE-INDICATOR			&maxUSIServiceIndicatorLength
		NUM-OF-BCSM-EVENT							&numOfBCSMEvents
		NUM-OF-BCUSM-EVENT							&numOfBCUSMEvents
		NUM-OF-CHARGING-EVENT						&numOfChargingEvents
		NUM-OF-CSAS									&numOfCSAs
		NUM-OF-CSS									&numOfCSs
		NUM-OF-EXTENSIONS							&numOfExtensions
		NUM-OF-GENERIC-NUMBERS						&numOfGenericNumbers
		NUM-OF-IN-SERVICE-COMPATIBILITY-ID			&numOfInServiceCompatibilityIndLength
		NUM-OF-LEGS									&numOfLegs
		NUM-OF-MESSAGE-IDS							&numOfMessageIDs
		MAXIMUM-FOR-AMOUNT							&maxAmount
		MAXIMUM-FOR-INITIAL-UNIT-INCREMENT			&maxInitialUnitIncrement
		MAXIMUM-FOR-SCALING-FACTOR					&maxScalingFactor
		MAXIMUM-FOR-SEGMENTS-PER-DATA-INTERVAL		&maxSegmentsPerDataInterval
		MAXIMUM-FOR-TIME-PER-INTERVAL				&maxTimePerInterval
		MAXIMUM-FOR-UNITS-PER-DATA-INTERVAL			&maxUnitsPerDataInterval
		MAXIMUM-FOR-UNITS-PER-INTERVAL				&maxUnitsPerInterval
		MAXIMUM-FOR-UB-USER-CREDIT					&ub-maxUserCredit
		MAXIMUM-FOR-UB-NB-CALL						&ub-nbCall
	}


	-- The following instance of the parameter bound is just an example
	networkSpecificBoundSet PARAMETERS-BOUND ::=
	{
		MINIMUM-FOR-ACH-BILLING-CHARGING			1	-- example value
		MAXIMUM-FOR-ACH-BILLING-CHARGING			5	-- example value
		MINIMUM-FOR-ASSOCIATION-RELEASE-INFO		1	-- example value
		MAXIMUM-FOR-ASSOCIATION-RELEASE-INFO		5	-- example value
		MINIMUM-FOR-ATTRIBUTES						1	-- example value
		MAXIMUM-FOR-ATTRIBUTES						5	-- example value
		MAXIMUM-FOR-BACKWARD-GVNS					1	-- example value
		MAXIMUM-FOR-BACKWARD-GVNS					5	-- example value
		MAXIMUM-FOR-BEARER-CAPABILITY				5	-- example value
		MINIMUM-FOR-CALLED-PARTY-BCD-NUMBER       1
		MAXIMUM-FOR-CALLED-PARTY-BCD-NUMBER      41
		MINIMUM-FOR-CALLED-PARTY-NUMBER           2
		MAXIMUM-FOR-CALLED-PARTY-NUMBER          18
		MINIMUM-FOR-CALLING-PARTY-BUSINESS-GROUP-ID	1	-- example value
		MAXIMUM-FOR-CALLING-PARTY-BUSINESS-GROUP-ID	5	-- example value
		MINIMUM-FOR-CALLING-PARTY-NUMBER          2
		MAXIMUM-FOR-CALLING-PARTY-NUMBER         10
		MINIMUM-FOR-CALLING-PARTY-SUBADDRESS		1	-- example value
		MAXIMUM-FOR-CALLING-PARTY-SUBADDRESS		5	-- example value
		MINIMUM-FOR-CALL-RESULT						1	-- example value
		MAXIMUM-FOR-CALL-RESULT						5	-- example value
		MINIMUM-FOR-CARRIER							1	-- example value
		MAXIMUM-FOR-CARRIER							5	-- example value
		MAXIMUM-FOR-CAUSE							4	-- example value
		MINIMUM-FOR-COMPONENT-RECEIVED-INFO		1 -- example value
		MAXIMUM-FOR-COMPONENT-RECEIVED-INFO		5 -- example value
		MINIMUM-FOR-DIGITS							1	-- example value
		MAXIMUM-FOR-DIGITS							20
		MINIMUM-FOR-DISPLAY							1	-- example value
		MAXIMUM-FOR-DISPLAY							5	-- example value
		MINIMUM-FOR-EVENT-SPECIFIC-CHARGING			1	-- example value
		MAXIMUM-FOR-EVENT-SPECIFIC-CHARGING			5	-- example value
		MINIMUM-FOR-EVENT-TYPE-CHARGING				1	-- example value
		MAXIMUM-FOR-EVENT-TYPE-CHARGING				5	-- example value
		MINIMUM-FOR-FCI-BILLING-CHARGING-CS-ONE		1	-- example value
		MAXIMUM-FOR-FCI-BILLING-CHARGING-CS-ONE		5	-- example value
		MINIMUM-FOR-FCI-BILLING-CHARGING-CS-TWO		1	-- example value
		MAXIMUM-FOR-FCI-BILLING-CHARGING-CS-TWO		5	-- example value
		MINIMUM-FOR-FORWARD-GVNS					1	-- example value
		MAXIMUM-FOR-FORWARD-GVNS					5	-- example value
		MINIMUM-FOR-GENERIC-NAME					1	-- example value
		MAXIMUM-FOR-GENERIC-NAME					5	-- example value
		MINIMUM-FOR-GENERIC-NUMBER					1	-- example value
		MAXIMUM-FOR-GENERIC-NUMBER					5	-- example value
		MAXIMUM-FOR-INITIAL-TIME-INTERVAL			5	-- example value
		MAXIMUM-FOR-IN-SERVICE-COMPATIBILITY		5	-- example value
		MINIMUM-FOR-IP-AVAILABLE					1	-- example value
		MAXIMUM-FOR-IP-AVAILABLE					5	-- example value
		MINIMUM-FOR-IP-SSP-CAPABILITIES				1	-- example value
		MAXIMUM-FOR-IP-SSP-CAPABILITIES				5	-- example value
		MINIMUM-FOR-ISDN-ACCESS-RELATED-INFO		1	-- example value
		MAXIMUM-FOR-ISDN-ACCESS-RELATED-INFO		5	-- example value
		MINIMUM-FOR-LOCATION-NUMBER					1	-- example value
		MAXIMUM-FOR-LOCATION-NUMBER					10	-- example value
		MINIMUM-FOR-MAIL-BOX-ID						1	-- example value
		MAXIMUM-FOR-MAIL-BOX-ID						5	-- example value
		MINIMUM-FOR-MESSAGE-CONTENT					1	-- example value
		MAXIMUM-FOR-MESSAGE-CONTENT					5	-- example value
		MINIMUM-FOR-MID-CALL-CONTROL-INFO			1	-- example value
		MAXIMUM-FOR-MID-CALL-CONTROL-INFO			5	-- example value
		MINIMUM-FOR-ORIGINAL-CALLED-PARTY-ID		1	-- example value
		MAXIMUM-FOR-ORIGINAL-CALLED-PARTY-ID		10	-- example value
		MINIMUM-FOR-REASON							1	-- example value
		MAXIMUM-FOR-REASON							5	-- example value
		MINIMUM-FOR-RECEIVED-INFORMATION			1	-- example value
		MAXIMUM-FOR-RECEIVED-INFORMATION			5	-- example value
		MAXIMUM-FOR-RECORDED-MESSAGE-UNITS			5	-- example value
		MAXIMUM-FOR-RECORDING-TIME					5	-- example value
		MINIMUM-FOR-REDIRECTING-ID					1	-- example value
		MAXIMUM-FOR-REDIRECTING-ID					10	-- example value
		MINIMUM-FOR-REGISTRATOR-IDENTIFIER			1	-- example value
		MAXIMUM-FOR-REGISTRATOR-IDENTIFIER			5	-- example value
		MINIMUM-FOR-REQUESTED-UTSI-NUM				1	-- example value
		MAXIMUM-FOR-REQUESTED-UTSI-NUM				5	-- example value
		MINIMUM-FOR-ROUTE-LIST						1	-- example value
		MAXIMUM-FOR-ROUTE-LIST						5	-- example value
		MINIMUM-FOR-SCF-ID							1	-- example value
		MAXIMUM-FOR-SCF-ID							5	-- example value
		MINIMUM-FOR-SCF-ADDRESS						1	-- example value
		MAXIMUM-FOR-SCF-ADDRESS						5	-- example value
		MINIMUM-FOR-SCI-BILLING-CHARGING			1	-- example value
		MAXIMUM-FOR-SCI-BILLING-CHARGING			5	-- example value
		MINIMUM-FOR-SII								1	-- example value
		MAXIMUM-FOR-SII								5	-- example value
		MINIMUM-FOR-SF-BILLING-CHARGING				1	-- example value
		MAXIMUM-FOR-SF-BILLING-CHARGING				5	-- example value
		MINIMUM-FOR-USI-INFORMATION					1	-- example value
		MAXIMUM-FOR-USI-INFORMATION					5	-- example value
		MINIMUM-FOR-USI-SERVICE-INDICATOR			1	-- example value
		MAXIMUM-FOR-USI-SERVICE-INDICATOR			5	-- example value
		NUM-OF-BCSM-EVENT							4	-- example value
		NUM-OF-BCUSM-EVENT							4	-- example value
		NUM-OF-CHARGING-EVENT						4	-- example value
		NUM-OF-CSAS									2	-- example value
		NUM-OF-CSS									2	-- example value
		NUM-OF-EXTENSIONS							1	-- example value
		NUM-OF-GENERIC-NUMBERS						2	-- example value
		NUM-OF-IN-SERVICE-COMPATIBILITY-ID			2	-- example value
		NUM-OF-LEGS									2	-- example value
		NUM-OF-MESSAGE-IDS							16	-- example value
		MAXIMUM-FOR-AMOUNT							2	-- example value
		MAXIMUM-FOR-INITIAL-UNIT-INCREMENT			2	-- example value
		MAXIMUM-FOR-SCALING-FACTOR					2	-- example value
		MAXIMUM-FOR-SEGMENTS-PER-DATA-INTERVAL		5	-- example value
		MAXIMUM-FOR-TIME-PER-INTERVAL				5	-- example value
		MAXIMUM-FOR-UNITS-PER-DATA-INTERVAL			5 	-- example value
		MAXIMUM-FOR-UNITS-PER-INTERVAL				5	-- example value
		MAXIMUM-FOR-UB-USER-CREDIT					5	-- example value
		MAXIMUM-FOR-UB-NB-CALL						5	-- example value
	}

END
