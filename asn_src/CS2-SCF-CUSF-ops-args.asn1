CS2-SCF-CUSF-ops-args {itu-t(0) identified-organization(4) etsi(0) inDomain(1) in-network(1) cs2(20) modules(0) in-cs2-scf-cusf-ops-args (15) version1(0)}

DEFINITIONS IMPLICIT TAGS ::= BEGIN

	IMPORTS
		OPERATION
	FROM Remote-Operations-Information-Objects ros-InformationObjects
		PARAMETERS-BOUND,
	FROM CS2-classes classes
		opcode-initiateAssociation,
		opcode-releaseAssociation,
		opcode-requestReportBCUSMEvent,
		opcode-initialAssociationDP,
		opcode-connectAssociation,
		opcode-continueAssociation,
		opcode-eventReportBCUSM
	FROM CS2-operationcodes operationcodes
		BCUSMEvent,
		CalledPartyNumber {},
		Cause {},
		Duration,
		ExtensionField,
		LegID,
		MiscCallInfo
	FROM CS2-datatypes datatypes
		missingCustomerRecord,
		missingParameter,
		parameterOutOfRange,
		systemFailure,
		taskRefused,
		unexpectedComponentSequence,
		unexpectedDataValue,
		unexpectedParameter,
		unknownLegID
	FROM CS2-errortypes errortypes
		classes,
		operationcodes,
		ros-InformationObjects,
		datatypes,
		errortypes
	FROM CS2-object-identifiers
			{itu-t(0) identified-organization(4) etsi(0) inDomain(1) in-network(1) cs2(20) modules(0) in-cs2-object-identifiers(17) version1(0)};

	connectAssociation  {PARAMETERS-BOUND : bound}  OPERATION	::= {
		ARGUMENT		ConnectAssociationArg {bound}
		RETURN RESULT	FALSE
		ERRORS 			{missingParameter |
						parameterOutOfRange |
						systemFailure |
						taskRefused |
						unexpectedComponentSequence |
						unexpectedDataValue |
						unexpectedParameter}
		CODE			opcode-connectAssociation
		}
	-- Direction: SCF -> CUSF, Timer: Tcoa
	-- This operation is used to request the CUSF to proceed with processing. Additional information
	-- which shall be used in further connection establishment is provided by the SCF.

	ConnectAssociationArg  {PARAMETERS-BOUND : bound}::= SEQUENCE {
		address			[0]	CalledPartyNumber {bound},
		extensions		[1]	SEQUENCE SIZE(1..bound.&numOfExtensions)
		                     OF ExtensionField OPTIONAL,
		...
		}

	continueAssociation  {PARAMETERS-BOUND : bound}  OPERATION	::= {
		ARGUMENT		ContinueAssociationArg {bound}			OPTIONAL TRUE
		RETURN RESULT	FALSE
		ERRORS 			{missingParameter |
						parameterOutOfRange |
						systemFailure |
						taskRefused |
						unexpectedComponentSequence |
						unexpectedDataValue |
						unexpectedParameter}
		CODE			opcode-continueAssociation
		}
	-- Direction: SCF -> CUSF, Timer: Tcona
	-- This operation is used to request the CUSF to proceed with processing. Additional information
	-- which is not related to further connection establishment may be  provided by the SCF.

	ContinueAssociationArg  {PARAMETERS-BOUND : bound}::= SEQUENCE {
		extensions		[0]	SEQUENCE SIZE(1..bound.&numOfExtensions) OF
			      													ExtensionField OPTIONAL,
		...
		}

	eventReportBCUSM {PARAMETERS-BOUND : bound}  OPERATION	::= {
		ARGUMENT		EventReportBCUSMArg {bound}
		RETURN RESULT	FALSE
		ALWAYS RESPONDS	FALSE
		CODE			opcode-eventReportBCUSM
		}
	-- Direction: CUSF -> SCF, Timer: Terbce
	-- This operation is used to notify the SCF of a call unrelated event previously requested by the
	-- SCF in a RequestReportBCUSMEvent operation.

	EventReportBCUSMArg  {PARAMETERS-BOUND : bound}::= SEQUENCE {
		eventTypeBCUSM					[0]	EventTypeBCUSM					OPTIONAL,
		eventSpecificInformationBCUSM	[1]	EventSpecificInformationBCUSM	OPTIONAL,
		miscCallInfo					[2]	MiscCallInfo				DEFAULT {messageType request},
		cUApplicationInd				[3]	CUApplicationInd				OPTIONAL,
		legID							[4] LegID							OPTIONAL,
		extensions						[5]	SEQUENCE SIZE(1..bound.&numOfExtensions) OF
																	ExtensionField OPTIONAL,
		...
		}

	initialAssociationDP  {PARAMETERS-BOUND : bound}  OPERATION	::= {
		ARGUMENT		InitialAssociationDPArg {bound}
		RETURN RESULT	FALSE
		ERRORS 			{missingCustomerRecord |
						missingParameter |
						parameterOutOfRange |
						systemFailure |
						taskRefused |
						unexpectedComponentSequence |
						unexpectedDataValue |
						unexpectedParameter}
		CODE			opcode-initialAssociationDP
		}
	-- Direction: CUSF -> SCF, Timer: Tiadp
	-- This operation is used after detection of a TDP to initiate a call unrelated association with the
	-- SCF.

	InitialAssociationDPArg  {PARAMETERS-BOUND : bound}::= SEQUENCE {
		serviceKey				[0]	ServiceKey,
		cUApplicationInd		[1]	CUApplicationInd					OPTIONAL,
		miscCallInfo			[2]	MiscCallIinfo						OPTIONAL,
		eventtypeBCUSM			[3]	EventTypeBCUSM						OPTIONAL,
		calledPartyNumber		[4]	CalledPartyNumber {bound}			OPTIONAL,
		callingPartyNumber		[5]	CallingPartyNumber {bound}			OPTIONAL,
		callingPartySubAddress	[6]	CallingPartySubAddress				OPTIONAL,
		highLayerCompatibility	[7]	HighLayerCompatibility				OPTIONAL,
		bearerCapability		[8]	BearerCapability {bound}			OPTIONAL,
		uSIServiceIndicator		[9]	USIServiceIndicator {bound}			OPTIONAL,
		uSIInformation			[10] USIInformation {bound}				OPTIONAL,
		extensions				[11] SEQUENCE SIZE(1..bound.&numOfExtensions) OF
			  														ExtensionField OPTIONAL,
		...
		}

	initiateAssociation  {PARAMETERS-BOUND : bound}  OPERATION	::= {
		ARGUMENT		InitiateAssociationArg {bound}
		RETURN RESULT	TRUE
		ERRORS 			{missingParameter |
						parameterOutOfRange |
						systemFailure |
						taskRefused |
						unexpectedComponentSequence |
						unexpectedDataValue |
						unexpectedParameter}
		CODE		opcode-initiateAssociation
		}
	-- Direction: SCF -> CUSF, Timer: Tia
	-- This operation is used for allowing the SCF to initiate a call unrelated association with the
	-- user. The subsequent operations can be sent in the same TCAP message in the following order:
	-- 	- the RequestReportBCUSMEvent operation if an answer from the CUSF is expected

	InitiateAssociationArg  {PARAMETERS-BOUND : bound}::= SEQUENCE {
		calledPartyNumber	[0]	CalledPartyNumber {bound},
		extensions			[1]	SEQUENCE SIZE(1..bound.&numOfExtensions) OF
			   												   ExtensionField OPTIONAL,
		uSIServiceIndicator	[2]	USIServiceIndicator {bound}						OPTIONAL,
		uSIInformation		[3]	USIInformation {bound}							OPTIONAL,
		...
		}

	releaseAssociation  {PARAMETERS-BOUND : bound}  OPERATION ::= {
		ARGUMENT		ReleaseAssociationArg {bound}
		RETURN RESULT	FALSE
		ALWAYS RESPONDS	FALSE
		CODE			opcode-releaseAssociation
		}
	--  Direction: SCF -> CUSF, Timer: Trel
	--  This operation is used to indicate to the CUSF to release the existing association between the
	--  user and the network, during the BCUSM suspended at a DP.

	ReleaseAssociationArg  {PARAMETERS-BOUND : bound}::= Cause {bound}

	requestReportBCUSMEvent  {PARAMETERS-BOUND : bound}  OPERATION ::= {
		ARGUMENT		RequestReportBCUSMEventArg {bound}
		RETURN RESULT	FALSE
		ERRORS		 	{missingParameter |
						parameterOutOfRange |
						systemFailure |
						taskRefused |
						unknownLegID |
						unexpectedComponentSequence |
						unexpectedDataValue |
						unexpectedParameter}
		CODE			opcode-requestReportBCUSMEvent
		}
	-- Direction: SCF -> CUSF, Timer: Trrbce
	-- This operation is used to request the CUSF to monitor a BCUSM DP.


	RequestReportBCUSMEventArg  {PARAMETERS-BOUND : bound}::= SEQUENCE{
		bcusmEvents		[0] SEQUENCE SIZE(1..bound.&numOfBCUSMEvents) OF BCUSMEvent,
		monitorDuration	[3] Duration	OPTIONAL,
		extensions	 	[4] SEQUENCE SIZE(1..bound.&numOfExtensions) OF ExtensionField OPTIONAL,
		cUDPCriteria	[5] CUApplicationInd											OPTIONAL,
		legID			[6] LegID														OPTIONAL,
		...
		}

END
