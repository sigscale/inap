CS2-SCF-SRF-pkgs-contracts-acs {itu-t(0) recommendation(0) q(17) 1228 modules(0) in-cs2-scf-srf-pkgs-contracts-acs(8) version1(0)}

DEFINITIONS ::= BEGIN

-- This module describes the operation-packages, contracts and application-contexts used
-- over the SCF-SRF interface.

	IMPORTS
		PARAMETERS-BOUND,
		networkSpecificBoundSet,
		emptyConnectionPackage
	FROM CS2-classes classes
		CONTRACT,
		OPERATION-PACKAGE,
		OPERATION
	FROM Remote-Operations-Information-Objects ros-InformationObjects
		TCMessage {}
	FROM TCAPMessages tc-Messages
		APPLICATION-CONTEXT,
		dialogue-abstract-syntax
	FROM TC-Notation-Extensions tc-NotationExtensions
		playAnnouncement {},
		promptAndReceiveMessage {},
		promptAndCollectUserInformation {},
		scriptClose {},
		scriptEvent {},
		scriptInformation {},
		scriptRun {},
		specializedResourceReport
	FROM CS2-SCF-SRF-ops-args scf-srf-Operations
		cancel {},
		assistRequestInstructions {}
	FROM CS2-SSF-SCF-ops-args ssf-scf-Operations
		srf-scfActivationOfAssistPackage {}
	FROM CS2-SSF-SCF-pkgs-contracts-acs ssf-scf-Protocol
		id-package-specializedResourceControl,
		id-ac-srf-scf,
		id-contract-srf-scf,
		id-package-srf-scfCancel,
		id-package-scriptControl,
		id-package-messageControl,
		id-as-basic-srf-scf,
		classes,
		ros-InformationObjects,
		tc-Messages,
		tc-NotationExtensions,
		scf-srf-Operations,
		ssf-scf-Operations,
		ssf-scf-Protocol
	FROM CS2-object-identifiers
			{itu-t(0) recommendation(0) q(17) 1228 modules(0) in-cs2-object-identifiers(17) version1(0)};

	-- Application Contexts

	srf-scf-ac APPLICATION-CONTEXT ::= {
		CONTRACT                 srf-scf-contract
		DIALOGUE MODE            structured
		TERMINATION              basic
		ABSTRACT SYNTAXES        {dialogue-abstract-syntax
		                            | srf-scf-abstract-syntax}
		APPLICATION CONTEXT NAME id-ac-srf-scf
	}

	-- Contracts

	srf-scf-contract CONTRACT ::= {
		CONNECTION            emptyConnectionPackage
		INITIATOR CONSUMER OF {srf-scfActivationOfAssistPackage {networkSpecificBoundSet}}
		RESPONDER CONSUMER OF {specializedResourceControlPackage {networkSpecificBoundSet}
		                         | srf-scfCancelPackage {networkSpecificBoundSet}
		                         | scriptControlPackage {networkSpecificBoundSet}
		                         | messageControlPackage {networkSpecificBoundSet}}
		ID							id-contract-srf-scf
	}

	-- specializedResourceControl package
	specializedResourceControlPackage {PARAMETERS-BOUND : bound} OPERATION-PACKAGE ::= {
		CONSUMER INVOKES	{playAnnouncement {bound}
		                     | promptAndCollectUserInformation {bound}}
		SUPPLIER INVOKES  {specializedResourceReport}
		ID                id-package-specializedResourceControl
	}

	-- srf-scfCancel package
	srf-scfCancelPackage {PARAMETERS-BOUND : bound} OPERATION-PACKAGE ::= {
		CONSUMER INVOKES {cancel {bound}}
		ID               id-package-srf-scfCancel
	}

	-- scriptControl package
	scriptControlPackage {PARAMETERS-BOUND : bound} OPERATION-PACKAGE ::= {
		CONSUMER INVOKES {scriptClose {bound}
		                    | scriptRun {bound}
		                    | scriptInformation {bound}}
		SUPPLIER INVOKES {scriptEvent {bound}}
		ID               id-package-scriptControl
	}

	-- messageControl package
	messageControlPackage {PARAMETERS-BOUND : bound} OPERATION-PACKAGE ::= {
		CONSUMER INVOKES {promptAndReceiveMessage {bound}}
		ID               id-package-messageControl
	}

	-- Abstract Syntaxes

	srf-scf-abstract-syntax ABSTRACT-SYNTAX ::= {
		BASIC-SRF-SCF-PDUs IDENTIFIED BY	id-as-basic-srf-scf
	}

	BASIC-SRF-SCF-PDUs ::= TCMessage {{SRF-SCF-Invokable},{SRF-SCF-Returnable}}

	SRF-SCF-Invokable OPERATION ::= {
			assistRequestInstructions {networkSpecificBoundSet}
			| cancel {networkSpecificBoundSet}
			| playAnnouncement {networkSpecificBoundSet}
			| promptAndCollectUserInformation {networkSpecificBoundSet}
			| scriptClose {networkSpecificBoundSet}
			| scriptEvent {networkSpecificBoundSet}
			| scriptInformation {networkSpecificBoundSet}
			| scriptRun {networkSpecificBoundSet}
			| specializedResourceReport
			| promptAndReceiveMessage {networkSpecificBoundSet}}

	SRF-SCF-Returnable OPERATION ::= {
			assistRequestInstructions {networkSpecificBoundSet}
			| cancel {networkSpecificBoundSet}
			| playAnnouncement {networkSpecificBoundSet}
			| promptAndCollectUserInformation {networkSpecificBoundSet}
			| scriptClose {networkSpecificBoundSet}
			| scriptInformation {networkSpecificBoundSet}
			| scriptRun {networkSpecificBoundSet}
			| promptAndReceiveMessage {networkSpecificBoundSet}}

END
