CS2-SDF-SDF-Protocol {itu-t(0) recommendation(0) q(17) 1228 module(0) in-cs2-sdf-sdf-Protocol(18) version1(0)}

DEFINITIONS ::= BEGIN
-- EXPORTS All --

-- The types and values defined in this module are exported for use in the other ASN.1 modules
-- contained within the Directory Specifications, and for the use of other applications which will
-- use them to access Directory services. Other applications may use them for their own purposes,
-- but this will not constrain extensions and modifications needed to maintain or improve the
-- Directory service.

	IMPORTS
		distributedOperations,
		directoryShadowAbstractService,
		dsp,
		protocolObjectIdentifiers
	FROM  UsefulDefinitions ds-UsefulDefinitions
		ROS-OBJECT-CLASS,
		CONTRACT,
		OPERATION-PACKAGE,
		CONNECTION-PACKAGE,
		OPERATION
	FROM Remote-Operations-Information-Objects ros-InformationObjects
		Bind {},
		Unbind {}
	FROM Remote-Operations-Generic-ROS-PDUs ros-genericPDUs
		TCMessage {}
	FROM TCAPMessages tc-Messages
		APPLICATION-CONTEXT,
		dialogue-abstract-syntax
	FROM TC-Notation-Extensions tc-NotationExtensions
		dSABind,
		chainedSearch,
		chainedAddEntry,
		chainedRemoveEntry,
		chainedModifyEntry,
		chained {}
	FROM DistributedOperations distributedOperations
		dSAShadowBind,
		coordinateShadowUpdate,
		updateShadow,
		requestShadowUpdate
	FROM DirectoryShadowAbstractService directoryShadowAbstractService
		execute
	FROM CS2-SCF-SDF-Operations scf-sdf-Operations
		inEmptyUnbind
	FROM CS2-classes classes
		inSESEAbstractSyntax
	FROM CS2-SCF-SDF-Protocol scf-sdf-Protocol
		id-rosObject-dspDSA,
		id-rosObject-initiatingConsumerDSA,
		id-rosObject-respondingSupplierDSA,
		id-rosObject-respondingConsumerDSA,
		id-rosObject-initiatingSupplierDSA,
		id-contract-indsp,
		id-contract-shadowConsumer,
		id-contract-shadowSupplier,
		id-package-dspConnection,
		id-package-inchainedModify,
		id-package-inchainedSearch,
		id-package-chainedExecute,
		id-package-dispConnection,
		id-package-shadowConsumer,
		id-package-shadowSupplier,
		id-as-indirectorySystemAS,
		id-as-indirectoryDSABindingAS,
		id-as-indirectoryShadowAS,
		id-as-indsaShadowBindingAS,
		id-ac-indirectorySystemAC,
		id-ac-inShadowSupplierInitiatedAC,
		id-ac-inShadowConsumerInitiatedAC,
		id-ac-inShadowSupplierInitiatedWith3seAC,
		id-ac-inShadowConsumerInitiatedWith3seAC,
		id-ac-indirectorySystemWith3seAC,
		ds-UsefulDefinitions,
		ros-InformationObjects,
		ros-genericPDUs,
		tc-Messages,
		tc-NotationExtensions,
		scf-sdf-Operations,
		scf-sdf-Protocol,
		classes
	FROM CS2-object-identifiers
			{itu-t(0) recommendation(0) q(17)  1228 module(0) in-cs2-object-identifiers(17) version1(0)}
		id-se-threewayse
	FROM ProtocolObjectIdentifiers protocolObjectIdentifiers
		dspContract
	FROM DirectorySystemProtocol dsp;

	dsp-dsa  ROS-OBJECT-CLASS ::= {
		BOTH		{indspContract}
		ID			id-rosObject-dspDSA}

	initiating-consumer-dsa  ROS-OBJECT-CLASS ::= {
		INITIATES		{shadowConsumerContract}
		ID				id-rosObject-initiatingConsumerDSA}

	responding-supplier-dsa  ROS-OBJECT-CLASS ::= {
		RESPONDS		{shadowConsumerContract}
		ID				id-rosObject-respondingSupplierDSA}

	initiating-supplier-dsa  ROS-OBJECT-CLASS ::= {
		INITIATES		{shadowSupplierContract}
		ID				id-rosObject-initiatingSupplierDSA}

	responding-consumer-dsa  ROS-OBJECT-CLASS ::= {
		RESPONDS		{shadowSupplierContract}
		ID				id-rosObject-respondingConsumerDSA}

	indspContract  CONTRACT ::= {
		CONNECTION		dspConnectionPackage
		INITIATOR CONSUMER OF	{inchainedModifyPackage | inchainedSearchPackage |
							   chainedExecutePackage}
		ID				id-contract-indsp}

	dspConnectionPackage  CONNECTION-PACKAGE ::= {
		BIND		dSABind
		UNBIND		in-DSAUnbind
		ID			id-package-dspConnection}

	in-DSAUnbind	OPERATION ::= 	inEmptyUnbind

	inchainedModifyPackage  OPERATION-PACKAGE ::= {
		CONSUMER INVOKES	{chainedAddEntry | chainedRemoveEntry | chainedModifyEntry}
		ID					id-package-inchainedModify}

	inchainedSearchPackage OPERATION-PACKAGE ::= {
		CONSUMER INVOKES	{chainedSearch}
		ID					id-package-inchainedSearch}

	chainedExecutePackage OPERATION-PACKAGE ::= {
		CONSUMER INVOKES	{chainedExecute}
		ID					id-package-chainedExecute}

	chainedExecute	OPERATION ::= chained {execute}

	shadowConsumerContract  CONTRACT ::= {
		CONNECTION			dispConnectionPackage
		INITIATOR CONSUMER OF	{shadowConsumerPackage}
		ID					id-contract-shadowConsumer}

	shadowSupplierContract  CONTRACT ::= {
		CONNECTION			dispConnectionPackage
		RESPONDER CONSUMER OF	{shadowSupplierPackage}
		ID					id-contract-shadowSupplier}

	dispConnectionPackage  CONNECTION-PACKAGE ::= {
		BIND		dSAShadowBind
		UNBIND		in-DSAShadowUnbind
		ID			id-package-dispConnection}

	in-DSAShadowUnbind	OPERATION ::= 	inEmptyUnbind

	shadowConsumerPackage  OPERATION-PACKAGE ::= {
		CONSUMER INVOKES	{requestShadowUpdate}
		SUPPLIER INVOKES	{updateShadow}
		ID					id-package-shadowConsumer}

	shadowSupplierPackage  OPERATION-PACKAGE ::= {
		SUPPLIER INVOKES	{coordinateShadowUpdate | updateShadow}
		ID					id-package-shadowSupplier}

	inDirectorySystemAbstractSyntax  ABSTRACT-SYNTAX ::= {
		BasicDSP-PDUs
		IDENTIFIED BY		id-as-indirectorySystemAS}

	BasicDSP-PDUs ::= TCMessage {{DSP-Invokable},{DSP-Returnable}}

	DSP-Invokable OPERATION ::= {chainedAddEntry | chainedRemoveEntry | chainedModifyEntry |
																	chainedSearch | chainedExecute}

	DSP-Returnable OPERATION ::= {chainedAddEntry | chainedRemoveEntry | chainedModifyEntry |
																	chainedSearch | chainedExecute}

	inDirectoryDSABindingAbstractSyntax  ABSTRACT-SYNTAX ::= {
		DSABinding-PDUs
		IDENTIFIED BY		id-as-indirectoryDSABindingAS}

	DSABinding-PDUs ::= CHOICE {
		bind		Bind {dSABind},
		unbind		Unbind {in-DSAUnbind}}

	inDirectoryShadowAbstractSyntax ABSTRACT-SYNTAX ::= {
		BasicDISP-PDUs
		IDENTIFIED BY		id-as-indirectoryShadowAS}

	BasicDISP-PDUs ::= TCMessage {{DISP-Invokable}, {DISP-Returnable}}

	DISP-Invokable OPERATION ::= {requestShadowUpdate | updateShadow | coordinateShadowUpdate}

	DISP-Returnable OPERATION ::= {requestShadowUpdate | updateShadow | coordinateShadowUpdate}

	inDirectoryDSAShadowBindingAbstractSyntax  ABSTRACT-SYNTAX ::= {
		DISPBinding-PDUs
		IDENTIFIED BY		id-as-indsaShadowBindingAS}

	DISPBinding-PDUs ::= CHOICE {
		bind 		Bind {dSAShadowBind},
		unbind		Unbind {in-DSAShadowUnbind}}

	inDirectorySystemAC APPLICATION-CONTEXT ::= 	{
		CONTRACT				indspContract
		DIALOGUE MODE			structured
		TERMINATION				basic
		ABSTRACT SYNTAXES		{dialogue-abstract-syntax |
								inDirectorySystemAbstractSyntax |
								inDirectoryDSABindingAbstractSyntax}
		APPLICATION CONTEXT NAME id-ac-indirectorySystemAC}

	inDirectorySystemWith3seAC APPLICATION-CONTEXT ::= 	{
		CONTRACT				dspContract
		DIALOGUE MODE			structured
		TERMINATION				basic
		ADDITIONAL ASE			{id-se-threewayse}
		ABSTRACT SYNTAXES		{dialogue-abstract-syntax |
								inDirectorySystemAbstractSyntax |
								inDirectoryDSABindingAbstractSyntax |
								inSESEAbstractSyntax}
		APPLICATION CONTEXT NAME	id-ac-indirectorySystemWith3seAC}

	inshadowSupplierInitiatedAC APPLICATION-CONTEXT ::= {
		CONTRACT				shadowSupplierContract
		DIALOGUE MODE			structured
		TERMINATION				basic
		ABSTRACT SYNTAXES		{dialogue-abstract-syntax |
								inDirectoryShadowAbstractSyntax |
								inDirectoryDSAShadowBindingAbstractSyntax}
		APPLICATION CONTEXT NAME	id-ac-inShadowSupplierInitiatedAC}

	inshadowSupplierInitiatedWith3seAC APPLICATION-CONTEXT ::= {
		CONTRACT				shadowSupplierContract
		DIALOGUE MODE			structured
		TERMINATION				basic
		ADDITIONAL ASE			{id-se-threewayse}
		ABSTRACT SYNTAXES		{dialogue-abstract-syntax |
								inDirectoryShadowAbstractSyntax |
								inDirectoryDSAShadowBindingAbstractSyntax |
								inSESEAbstractSyntax}
		APPLICATION CONTEXT NAME	id-ac-inShadowSupplierInitiatedWith3seAC}

	inshadowConsumerInitiatedAC APPLICATION-CONTEXT ::= {
		CONTRACT				shadowConsumerContract
		DIALOGUE MODE			structured
		TERMINATION				basic
		ABSTRACT SYNTAXES		{dialogue-abstract-syntax |
								inDirectoryShadowAbstractSyntax |
								inDirectoryDSAShadowBindingAbstractSyntax}
		APPLICATION CONTEXT NAME	id-ac-inShadowConsumerInitiatedAC}

	inshadowConsumerInitiatedWith3seAC APPLICATION-CONTEXT ::= {
		CONTRACT				shadowConsumerContract
		DIALOGUE MODE			structured
		TERMINATION				basic
		ADDITIONAL ASE			{id-se-threewayse}
		ABSTRACT SYNTAXES		{dialogue-abstract-syntax |
								inDirectoryShadowAbstractSyntax |
								inDirectoryDSAShadowBindingAbstractSyntax |
								inSESEAbstractSyntax}
		APPLICATION CONTEXT NAME	id-ac-inShadowConsumerInitiatedWith3seAC}

END
